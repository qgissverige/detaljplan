FME workspace plan2gis_v2_p.fmw

Parameters:
- SourceDataset_GML = $(FME_MF_DIR)plankarta.xml   # Source Geography Markup Language (GML) File(s)
- SourceDataset_XML = $(FME_MF_DIR)plankarta.xml   # Source XML File(s)
- SourceDataset_XML_9 = $(FME_MF_DIR)plankarta.xml   # Source XML File(s)
- SourceDataset_XML_13 = $(FME_MF_DIR)plankarta.xml   # Source XML File(s)
- SourceDataset_XML_11 = $(FME_MF_DIR)plankarta.xml   # Source XML File(s)
- SourceDataset_XML_8 = $(FME_MF_DIR)plankarta.xml   # Source XML File(s)
- SourceDataset_XML_10 = $(FME_MF_DIR)plankarta.xml   # Source XML File(s)
- SourceDataset_XML_12 = $(FME_MF_DIR)plankarta.xml   # Source XML File(s)
- DestDataset_POSTGIS = databas   # Database
- DestDataset_POSTGRES = databas   # Database

Readers:
- GML_1: GML from $(SourceDataset_GML) in EPSG:3008
- XML_1: XML from $(SourceDataset_XML_13)
- XML_2: XML from $(SourceDataset_XML)
- XML_3: XML from $(SourceDataset_XML_9)
- XML_4: XML from $(SourceDataset_XML_11)
- XML_5: XML from $(SourceDataset_XML_8)
- XML_6: XML from $(SourceDataset_XML_10)
- XML_7: XML from $(SourceDataset_XML_12)

Writers:
- POSTGIS_1: POSTGIS to $(DestDataset_POSTGIS)
- POSTGRES_1: POSTGRES to $(DestDataset_POSTGRES)

DP_Plan (reader XML_1)
    attributes: DP_Plan.gml xml_char(31), DP_Plan.id xml_char(4), DP_Plan.xmlns xml_char(27), anvandningsbestammelse{}.DP_Anvandningsbestammelse.administrativBestammelse{}.DP_AdministrativBestammelse.bestammelseid xml_decimal(3,0), anvandningsbestammelse{}.DP_Anvandningsbestammelse.administrativBestammelse{}.DP_AdministrativBestammelse.bestammelsetyp xml_char(27), anvandningsbestammelse{}.DP_Anvandningsbestammelse.administrativBestammelse{}.DP_AdministrativBestammelse.beteckning xml_char(2), anvandningsbestammelse{}.DP_Anvandningsbestammelse.administrativBestammelse{}.DP_AdministrativBestammelse.gml xml_char(31), anvandningsbestammelse{}.DP_Anvandningsbestammelse.administrativBestammelse{}.DP_AdministrativBestammelse.id xml_char(4), anvandningsbestammelse{}.DP_Anvandningsbestammelse.administrativBestammelse{}.DP_AdministrativBestammelse.insattning.Point.id xml_char(4), anvandningsbestammelse{}.DP_Anvandningsbestammelse.administrativBestammelse{}.DP_AdministrativBestammelse.insattning.Point.pos xml_char(25), anvandningsbestammelse{}.DP_Anvandningsbestammelse.administrativBestammelse{}.DP_AdministrativBestammelse.insattning.Point.pos.srsDimension xml_decimal(2,0), anvandningsbestammelse{}.DP_Anvandningsbestammelse.administrativBestammelse{}.DP_AdministrativBestammelse.omrade xml_char(1), anvandningsbestammelse{}.DP_Anvandningsbestammelse.administrativBestammelse{}.DP_AdministrativBestammelse.omrade.href xml_char(3), anvandningsbestammelse{}.DP_Anvandningsbestammelse.administrativBestammelse{}.DP_AdministrativBestammelse.rotation xml_decimal(2,0), anvandningsbestammelse{}.DP_Anvandningsbestammelse.administrativBestammelse{}.DP_AdministrativBestammelse.uuid xml_char(37), anvandningsbestammelse{}.DP_Anvandningsbestammelse.administrativBestammelse{}.DP_AdministrativBestammelse.xmlns xml_char(27), anvandningsbestammelse{}.DP_Anvandningsbestammelse.anvandningsslag xml_char(20), anvandningsbestammelse{}.DP_Anvandningsbestammelse.bestammelseid xml_decimal(3,0), anvandningsbestammelse{}.DP_Anvandningsbestammelse.beteckning xml_char(6), anvandningsbestammelse{}.DP_Anvandningsbestammelse.egenskapsbestammelse{}.DP_Egenskapsbestammelse.bestammelseid xml_decimal(3,0), anvandningsbestammelse{}.DP_Anvandningsbestammelse.egenskapsbestammelse{}.DP_Egenskapsbestammelse.bestammelsetyp xml_char(33), anvandningsbestammelse{}.DP_Anvandningsbestammelse.egenskapsbestammelse{}.DP_Egenskapsbestammelse.beteckning xml_char(3), anvandningsbestammelse{}.DP_Anvandningsbestammelse.egenskapsbestammelse{}.DP_Egenskapsbestammelse.gml xml_char(31), anvandningsbestammelse{}.DP_Anvandningsbestammelse.egenskapsbestammelse{}.DP_Egenskapsbestammelse.id xml_char(4), anvandningsbestammelse{}.DP_Anvandningsbestammelse.egenskapsbestammelse{}.DP_Egenskapsbestammelse.index xml_decimal(5,0), anvandningsbestammelse{}.DP_Anvandningsbestammelse.egenskapsbestammelse{}.DP_Egenskapsbestammelse.insattning.Point.id xml_char(4), anvandningsbestammelse{}.DP_Anvandningsbestammelse.egenskapsbestammelse{}.DP_Egenskapsbestammelse.insattning.Point.pos xml_char(25), anvandningsbestammelse{}.DP_Anvandningsbestammelse.egenskapsbestammelse{}.DP_Egenskapsbestammelse.insattning.Point.pos.srsDimension xml_decimal(2,0), anvandningsbestammelse{}.DP_Anvandningsbestammelse.egenskapsbestammelse{}.DP_Egenskapsbestammelse.omrade xml_char(1), anvandningsbestammelse{}.DP_Anvandningsbestammelse.egenskapsbestammelse{}.DP_Egenskapsbestammelse.omrade.href xml_char(4),
      anvandningsbestammelse{}.DP_Anvandningsbestammelse.egenskapsbestammelse{}.DP_Egenskapsbestammelse.rotation xml_decimal(2,0), anvandningsbestammelse{}.DP_Anvandningsbestammelse.egenskapsbestammelse{}.DP_Egenskapsbestammelse.uuid xml_char(37), anvandningsbestammelse{}.DP_Anvandningsbestammelse.egenskapsbestammelse{}.DP_Egenskapsbestammelse.variabel.DP_VarDecimaltal.namn xml_char(13), anvandningsbestammelse{}.DP_Anvandningsbestammelse.egenskapsbestammelse{}.DP_Egenskapsbestammelse.variabel.DP_VarDecimaltal.varde xml_decimal(5,0), anvandningsbestammelse{}.DP_Anvandningsbestammelse.egenskapsbestammelse{}.DP_Egenskapsbestammelse.variabel.DP_VarText.namn xml_char(18), anvandningsbestammelse{}.DP_Anvandningsbestammelse.egenskapsbestammelse{}.DP_Egenskapsbestammelse.variabel.DP_VarText.varde xml_char(76), anvandningsbestammelse{}.DP_Anvandningsbestammelse.egenskapsbestammelse{}.DP_Egenskapsbestammelse.xmlns xml_char(27), anvandningsbestammelse{}.DP_Anvandningsbestammelse.gml xml_char(31), anvandningsbestammelse{}.DP_Anvandningsbestammelse.huvudsaklig xml_char(5), anvandningsbestammelse{}.DP_Anvandningsbestammelse.id xml_char(4), anvandningsbestammelse{}.DP_Anvandningsbestammelse.index xml_decimal(2,0), anvandningsbestammelse{}.DP_Anvandningsbestammelse.insattning.Point.id xml_char(4), anvandningsbestammelse{}.DP_Anvandningsbestammelse.insattning.Point.pos xml_char(25), anvandningsbestammelse{}.DP_Anvandningsbestammelse.insattning.Point.pos.srsDimension xml_decimal(2,0), anvandningsbestammelse{}.DP_Anvandningsbestammelse.omrade xml_char(1), anvandningsbestammelse{}.DP_Anvandningsbestammelse.omrade.href xml_char(3), anvandningsbestammelse{}.DP_Anvandningsbestammelse.precisering xml_char(12), anvandningsbestammelse{}.DP_Anvandningsbestammelse.rotation xml_decimal(16,12), anvandningsbestammelse{}.DP_Anvandningsbestammelse.uuid xml_char(37), anvandningsbestammelse{}.DP_Anvandningsbestammelse.xmlns xml_char(27), forslag xml_boolean, generellPlanbestammelse{}.DP_AdministrativBestammelse.bestammelseid xml_decimal(2,0), generellPlanbestammelse{}.DP_AdministrativBestammelse.bestammelsetyp xml_char(22), generellPlanbestammelse{}.DP_AdministrativBestammelse.gml xml_char(31), generellPlanbestammelse{}.DP_AdministrativBestammelse.id xml_char(3), generellPlanbestammelse{}.DP_AdministrativBestammelse.insattning.Point.id xml_char(3), generellPlanbestammelse{}.DP_AdministrativBestammelse.insattning.Point.pos xml_char(24), generellPlanbestammelse{}.DP_AdministrativBestammelse.insattning.Point.pos.srsDimension xml_decimal(2,0), generellPlanbestammelse{}.DP_AdministrativBestammelse.omrade xml_char(1), generellPlanbestammelse{}.DP_AdministrativBestammelse.omrade.href xml_char(6),
      generellPlanbestammelse{}.DP_AdministrativBestammelse.rotation xml_decimal(2,0), generellPlanbestammelse{}.DP_AdministrativBestammelse.uuid xml_char(37), generellPlanbestammelse{}.DP_AdministrativBestammelse.variabel.DP_VarHeltal.namn xml_char(6), generellPlanbestammelse{}.DP_AdministrativBestammelse.variabel.DP_VarHeltal.varde xml_decimal(2,0), generellPlanbestammelse{}.DP_AdministrativBestammelse.xmlns xml_char(27), hojdsystem xml_char(8), katalog xml_char(9), katalogversion xml_char(11), kommun xml_decimal(5,0), koordinatsystem xml_char(15), planid xml_char(10), plannamn xml_char(38), planomrade xml_char(1), planomrade.href xml_char(6), plantyp xml_char(3), registerstatus xml_boolean, registreringsdatum xml_char(17), uuid xml_char(37), xml_fragment xml_xml, xml_id xml_char(18), xml_matched_element xml_char(8), xml_parent_child_pos xml_char(1), xml_parent_id xml_char(1)
    -> AttributeKeeper_3
AttributeKeeper_3
    KEEP_ATTRS = planomrade.href,katalogversion,registreringsdatum,koordinatsystem,kommun,registerstatus,fme_feature_type,plannamn,uuid,forslag,plantyp,katalog,planid,hojdsystem
    -> AttributeRenamer_3
AttributeRenamer_3
    ATTR_TABLE = RENAME_SET_DEFAULT planomrade.href > omrade.href
    -> VariableSetter
VariableSetter
    VARNAME = plan_uuid
    VALUE = @Value(uuid)
    SCOPE = Global
    -> AttributeTrimmer_2
DP_Anvandningsbestammelse (reader XML_3)
    attributes: DP_Anvandningsbestammelse.gml xml_char(31), DP_Anvandningsbestammelse.id xml_char(4), DP_Anvandningsbestammelse.xmlns xml_char(27), administrativBestammelse{}.DP_AdministrativBestammelse.bestammelseid xml_decimal(3,0), administrativBestammelse{}.DP_AdministrativBestammelse.bestammelsetyp xml_char(27), administrativBestammelse{}.DP_AdministrativBestammelse.beteckning xml_char(2), administrativBestammelse{}.DP_AdministrativBestammelse.gml xml_char(31), administrativBestammelse{}.DP_AdministrativBestammelse.id xml_char(4), administrativBestammelse{}.DP_AdministrativBestammelse.insattning.Point.id xml_char(4), administrativBestammelse{}.DP_AdministrativBestammelse.insattning.Point.pos xml_char(25), administrativBestammelse{}.DP_AdministrativBestammelse.insattning.Point.pos.srsDimension xml_decimal(2,0), administrativBestammelse{}.DP_AdministrativBestammelse.omrade xml_char(1), administrativBestammelse{}.DP_AdministrativBestammelse.omrade.href xml_char(3), administrativBestammelse{}.DP_AdministrativBestammelse.rotation xml_decimal(2,0), administrativBestammelse{}.DP_AdministrativBestammelse.uuid xml_char(37), administrativBestammelse{}.DP_AdministrativBestammelse.xmlns xml_char(27), anvandningsslag xml_char(20), bestammelseid xml_decimal(3,0), beteckning xml_char(6), egenskapsbestammelse{}.DP_Egenskapsbestammelse.bestammelseid xml_decimal(3,0), egenskapsbestammelse{}.DP_Egenskapsbestammelse.bestammelsetyp xml_char(33), egenskapsbestammelse{}.DP_Egenskapsbestammelse.beteckning xml_char(3), egenskapsbestammelse{}.DP_Egenskapsbestammelse.gml xml_char(31), egenskapsbestammelse{}.DP_Egenskapsbestammelse.id xml_char(4), egenskapsbestammelse{}.DP_Egenskapsbestammelse.index xml_decimal(5,0), egenskapsbestammelse{}.DP_Egenskapsbestammelse.insattning.Point.id xml_char(4), egenskapsbestammelse{}.DP_Egenskapsbestammelse.insattning.Point.pos xml_char(25), egenskapsbestammelse{}.DP_Egenskapsbestammelse.insattning.Point.pos.srsDimension xml_decimal(2,0), egenskapsbestammelse{}.DP_Egenskapsbestammelse.omrade xml_char(1), egenskapsbestammelse{}.DP_Egenskapsbestammelse.omrade.href xml_char(4),
      egenskapsbestammelse{}.DP_Egenskapsbestammelse.rotation xml_decimal(2,0), egenskapsbestammelse{}.DP_Egenskapsbestammelse.uuid xml_char(37), egenskapsbestammelse{}.DP_Egenskapsbestammelse.variabel.DP_VarDecimaltal.namn xml_char(13), egenskapsbestammelse{}.DP_Egenskapsbestammelse.variabel.DP_VarDecimaltal.varde xml_decimal(5,0), egenskapsbestammelse{}.DP_Egenskapsbestammelse.variabel.DP_VarText.namn xml_char(18), egenskapsbestammelse{}.DP_Egenskapsbestammelse.variabel.DP_VarText.varde xml_char(76), egenskapsbestammelse{}.DP_Egenskapsbestammelse.xmlns xml_char(27), huvudsaklig xml_char(5), index xml_decimal(2,0), insattning.Point.id xml_char(4), insattning.Point.pos xml_char(25), insattning.Point.pos.srsDimension xml_decimal(2,0), omrade xml_char(1), omrade.href xml_char(3), precisering xml_char(12), rotation xml_decimal(16,12), uuid xml_char(37), xml_fragment xml_xml, xml_id xml_char(41), xml_matched_element xml_char(26), xml_parent_child_pos xml_char(1), xml_parent_id xml_char(1)
    -> AttributeKeeper_2
AttributeKeeper_2
    KEEP_ATTRS = huvudsaklig,insattning.Point.pos,beteckning,rotation,precisering,omrade.href,fme_feature_type,insattning.Point.id,uuid,index,bestammelseid,anvandningsslag
    -> extract_position_3 [AttributeSplitter_Input]
DP_Egenskapsbestammelse (reader XML_5)
    attributes: DP_Egenskapsbestammelse.gml xml_char(31), DP_Egenskapsbestammelse.id xml_char(4), DP_Egenskapsbestammelse.xmlns xml_char(27), bestammelseid xml_decimal(3,0), bestammelsetyp xml_char(33), beteckning xml_char(3), index xml_decimal(5,0), insattning.Point.id xml_char(4), insattning.Point.pos xml_char(25), insattning.Point.pos.srsDimension xml_decimal(2,0), omrade xml_char(1), omrade.href xml_char(4), rotation xml_decimal(2,0), uuid xml_char(37), variabel.DP_VarDecimaltal.namn xml_char(13), variabel.DP_VarDecimaltal.varde xml_decimal(5,0), variabel.DP_VarText.namn xml_char(18), variabel.DP_VarText.varde xml_char(76), xml_fragment xml_xml, xml_id xml_char(44), xml_matched_element xml_char(24), xml_parent_child_pos xml_char(1), xml_parent_id xml_char(1)
    -> AttributeKeeper_5
AttributeKeeper_5
    KEEP_ATTRS = insattning.Point.pos,variabel.DP_VarText.namn,beteckning,rotation,variabel.DP_VarDecimaltal.varde,omrade.href,DP_Egenskapsbestammelse.id,bestammelsetyp,fme_feature_type,uuid,index,variabel.DP_VarDecimaltal.namn,bestammelseid,variabel.DP_VarText.varde
    -> DuplicateFilter
DP_AdministrativBestammelse (reader XML_6)
    attributes: DP_AdministrativBestammelse.gml xml_char(31), DP_AdministrativBestammelse.id xml_char(4), DP_AdministrativBestammelse.xmlns xml_char(27), bestammelseid xml_decimal(3,0), bestammelsetyp xml_char(27), beteckning xml_char(2), insattning.Point.id xml_char(4), insattning.Point.pos xml_char(25), insattning.Point.pos.srsDimension xml_decimal(2,0), omrade xml_char(1), omrade.href xml_char(3), rotation xml_decimal(2,0), uuid xml_char(37), xml_fragment xml_xml, xml_id xml_char(48), xml_matched_element xml_char(28), xml_parent_child_pos xml_char(1), xml_parent_id xml_char(1)
    -> AttributeKeeper_6
AttributeKeeper_6
    KEEP_ATTRS = uuid,beteckning,DP_AdministrativBestammelse.id,bestammelseid,rotation,bestammelsetyp,insattning.Point.pos,fme_basename,omrade.href
    -> DuplicateFilter
DuplicateFilter
    INPUT_ORDERED_CHOICE = No
    KEYATTR = insattning.Point.pos omrade.href rotation bestammelsetyp beteckning variabel.DP_VarText.namn variabel.DP_VarDecimaltal.namn index variabel.DP_VarDecimaltal.varde variabel.DP_VarText.varde
    UNIQUE -> extract_position_3 [AttributeSplitter_Input]
    UNIQUE -> AttributeManager_2
DP_AdministrativBestammelse (reader XML_4)
    attributes: DP_AdministrativBestammelse.gml xml_char(31), DP_AdministrativBestammelse.id xml_char(3), DP_AdministrativBestammelse.xmlns xml_char(27), bestammelseid xml_decimal(2,0), bestammelsetyp xml_char(22), insattning.Point.id xml_char(3), insattning.Point.pos xml_char(24), insattning.Point.pos.srsDimension xml_decimal(2,0), omrade xml_char(1), omrade.href xml_char(6), rotation xml_decimal(2,0), uuid xml_char(37), variabel.DP_VarHeltal.namn xml_char(6), variabel.DP_VarHeltal.varde xml_decimal(2,0), xml_fragment xml_xml, xml_id xml_char(43), xml_matched_element xml_char(28), xml_parent_child_pos xml_char(1), xml_parent_id xml_char(1)
    -> AttributeCreator
AttributeCreator
    ATTR_TABLE = SET_TO fme_feature_type = DP_GenerellBestammelse
    -> AttributeKeeper_4
AttributeKeeper_4
    KEEP_ATTRS = DP_AdministrativBestammelse.id,insattning.Point.pos,rotation,omrade.href,bestammelsetyp,fme_feature_type,uuid,bestammelseid,variabel.DP_VarHeltal.varde,variabel.DP_VarHeltal.namn
    -> extract_position_3 [AttributeSplitter_Input]
    -> AttributeManager_2
extract_position_3
    INSATTNING.POINT.POS = @Value(insattning.Point.pos)
    ListIndexer_2_Output -> AttributeTrimmer_2
AttributeTrimmer_2
    SRC_ATTRS = omrade.href
    TRIM_CHARS = #
    TRIM_TYPE = Both
    TRIM_TO_NONE = Yes
    -> merge_yta_best [REQUESTOR]
merge_yta_best: FeatureMerger
    JOIN_KEYS = @Value(omrade.href) @Value(DP_Omrade.id) AUTO
    PROCESS_DUPS = No
    MERGE_TYPE = Attributes and Geometry
    REJECT_NULL_MISSING_KEYS = No
    IGNORE_NULLS = No
    ATTR_CONFLICT_RES = Use Requestor
    SUPPLIERS_FIRST = No
    ATTR_ACCUM_MODE = Merge Supplier
    MERGED -> DuplicateFilter_3
    MERGED -> AttributeFilter
AttributeFilter
    ATTR_NAME = fme_feature_type
    ATTR_VALUES = <Empty>,<Missing>,<Null>,<Unfiltered>,DP_Plan,DP_Anvandningsbestammelse,DP_Egenskapsbestammelse,DP_AdministrativBestammelse,DP_GenerellBestammelse
    DP_Plan -> poc2_plan (writer POSTGRES_1)
    DP_Plan -> plan.poc_planyta (writer POSTGIS_1)
    DP_Anvandningsbestammelse -> poc_anv_best (writer POSTGRES_1)
    DP_Egenskapsbestammelse -> poc_eg_best (writer POSTGRES_1)
    DP_AdministrativBestammelse -> poc_admin_best (writer POSTGRES_1)
    DP_GenerellBestammelse -> poc_generell_best (writer POSTGRES_1)
plan.poc_planyta (writer POSTGIS_1)
    attributes: planid text, plannamn text, plantyp text, forslag bool, kommun int4, koordinatsystem text, hojdsystem text, registreringsdatum date, registerstatus varchar(1), katalog text, katalogversion text, uuid uuid,PrimaryKey
poc2_plan (writer POSTGRES_1)
    attributes: planid text, plannamn text, plantyp text, forslag bool, kommun int4, koordinatsystem text, hojdsystem text, registreringsdatum date, registerstatus varchar(1), katalog text, katalogversion text, uuid uuid,PrimaryKey
poc_anv_best (writer POSTGRES_1)
    attributes: uuid uuid,PrimaryKey, anvandningsslag varchar(20), beteckning varchar(20), index int2, precisering varchar(100), huvudsaklig bool, norr numeric(10,3), ost numeric(10,3), rotation numeric(10,3), ey_uuid uuid,BTree, plan_uuid uuid
poc_eg_best (writer POSTGRES_1)
    attributes: uuid uuid,PrimaryKey, bestammelsetyp text, beteckning text, index text, norr numeric(10,3), ost numeric(10,3), rotation numeric(10,3), ey_uuid uuid, plan_uuid uuid
poc_admin_best (writer POSTGRES_1)
    attributes: uuid uuid,PrimaryKey, bestammelsetyp text, beteckning text, index text, norr numeric(10,3), ost numeric(10,3), rotation numeric(10,3), ey_uuid uuid, plan_uuid uuid
poc_generell_best (writer POSTGRES_1)
    attributes: uuid uuid,PrimaryKey, bestammelsetyp text, beteckning text, index text, norr numeric(10,3), ost numeric(10,3), rotation numeric(10,3), ey_uuid uuid, plan_uuid uuid
DuplicateFilter_3
    INPUT_ORDERED_CHOICE = No
    KEYATTR = ey_uuid
    UNIQUE -> poc2_omrade_yta (writer POSTGIS_1)
    UNIQUE -> AttributeFilter_2
poc2_omrade_yta (writer POSTGIS_1)
    attributes: ey_uuid uuid,PrimaryKey, plan_uuid uuid,BTree
AttributeFilter_2
    ATTR_NAME = fme_feature_type
    ATTR_VALUES = <Empty>,<Missing>,<Null>,<Unfiltered>,DP_Plan,DP_Anvandningsbestammelse,DP_Egenskapsbestammelse,DP_AdministrativBestammelse,DP_GenerellBestammelse
    DP_Anvandningsbestammelse -> plan.poc_anv_yta (writer POSTGIS_1)
    DP_Egenskapsbestammelse -> plan.poc_eg_yta (writer POSTGIS_1)
    DP_AdministrativBestammelse -> plan.poc_admin_yta (writer POSTGIS_1)
plan.poc_anv_yta (writer POSTGIS_1)
    attributes: ey_uuid uuid,PrimaryKey, plan_uuid uuid,BTree
plan.poc_eg_yta (writer POSTGIS_1)
    attributes: ey_uuid uuid,PrimaryKey, plan_uuid uuid
plan.poc_admin_yta (writer POSTGIS_1)
    attributes: ey_uuid uuid,PrimaryKey, plan_uuid uuid
AttributeManager_2
    ATTR_TABLE:
      RENAME_SET_VALUE DP_AdministrativBestammelse.id > Bestammelse_id
      REMOVE bestammelseid
      REMOVE bestammelsetyp
      RENAME_SET_VALUE uuid > best_uuid
      REMOVE variabel.DP_VarHeltal.namn
      REMOVE variabel.DP_VarHeltal.varde
      RENAME_SET_VALUE DP_Egenskapsbestammelse.id > Bestammelse_id
      REMOVE beteckning
      REMOVE index
      REMOVE insattning.Point.pos
      REMOVE omrade.href
      REMOVE rotation
      REMOVE variabel.DP_VarDecimaltal.namn
      REMOVE variabel.DP_VarDecimaltal.varde
      REMOVE variabel.DP_VarText.namn
      REMOVE variabel.DP_VarText.varde
    -> FeatureMerger_4 [SUPPLIER]
variabel (reader XML_7)
    attributes: DP_AdministrativBestammelse.gml xml_char(31), DP_AdministrativBestammelse.id xml_char(3), DP_AdministrativBestammelse.xmlns xml_char(27), DP_Egenskapsbestammelse.gml xml_char(31), DP_Egenskapsbestammelse.id xml_char(4), DP_Egenskapsbestammelse.xmlns xml_char(27), DP_VarDecimaltal.namn xml_char(13), DP_VarDecimaltal.varde xml_decimal(5,0), DP_VarHeltal.namn xml_char(6), DP_VarHeltal.varde xml_decimal(2,0), DP_VarText.namn xml_char(18), DP_VarText.varde xml_char(76), xml_fragment xml_xml, xml_id xml_char(31), xml_matched_element xml_char(9), xml_parent_child_pos xml_char(1), xml_parent_id xml_char(1)
    -> AttributeManager
AttributeManager
    ATTR_TABLE:
      REMOVE DP_AdministrativBestammelse.gml
      RENAME_SET_VALUE DP_AdministrativBestammelse.id > Bestammelse_id
      REMOVE DP_AdministrativBestammelse.xmlns
      REMOVE DP_Egenskapsbestammelse.gml
      RENAME_SET_VALUE DP_Egenskapsbestammelse.id > Bestammelse_id
      REMOVE DP_Egenskapsbestammelse.xmlns
      RENAME_SET_VALUE DP_VarDecimaltal.namn > namn
      RENAME_SET_VALUE DP_VarDecimaltal.varde > varde_dec
      RENAME_SET_VALUE DP_VarHeltal.namn > namn
      RENAME_SET_VALUE DP_VarHeltal.varde > varde_hel
      RENAME_SET_VALUE DP_VarText.namn > namn
      RENAME_SET_VALUE DP_VarText.varde > varde_txt
      REMOVE xml_fragment
      REMOVE xml_id
      REMOVE xml_matched_element
      REMOVE xml_parent_child_pos
      REMOVE xml_parent_id
    -> FeatureMerger_4 [REQUESTOR]
FeatureMerger_4
    JOIN_KEYS = @Value(Bestammelse_id) @Value(Bestammelse_id) AUTO
    PROCESS_DUPS = No
    MERGE_TYPE = Attributes Only
    REJECT_NULL_MISSING_KEYS = No
    IGNORE_NULLS = No
    ATTR_CONFLICT_RES = Use Requestor
    SUPPLIERS_FIRST = No
    ATTR_ACCUM_MODE = Merge Supplier
    MERGED -> poc_variabel (writer POSTGRES_1)
poc_variabel (writer POSTGRES_1)
    attributes: id serial,PrimaryKey, namn text, varde_dec numeric(10,3), varde_hel int4, varde_txt text, best_uuid uuid

Bookmark: Skapa planområdena
DP_Grans (reader GML_1)
    attributes: typ{} xml_char(5), linje xml_geometry
    -> ListIndexer
ListIndexer
    PREFIX = typ
    LIST_ATTR = typ{}
    INDEX = 0
    -> FeatureMerger [SUPPLIER]
    -> poc_grans (writer POSTGIS_1)
poc_grans (writer POSTGIS_1)
    attributes: id serial,PrimaryKey, typ varchar(10)
DP_Omrade (reader XML_2)
    attributes: DP_Omrade.gml xml_char(31), DP_Omrade.id xml_char(5), DP_Omrade.xlink xml_char(29), DP_Omrade.xmlns xml_char(27), minus xml_char(1), minus.href xml_char(5), minus{} xml_char(1), minus{}.href xml_char(5), plus{} xml_char(1), plus{}.href xml_char(5), xml_fragment xml_xml, xml_id xml_char(20), xml_matched_element xml_char(10), xml_parent_child_pos xml_char(1), xml_parent_id xml_char(1)
    -> ListExploder_minus
    -> ListExploder_plus
ListExploder_minus
    INDEX_ATTR = _element_index_minus
    LIST_ATTR = minus{}
    ATTR_CONFLICT_RES = Use List Attribute Values
    ATTR_ACCUM_MODE = Merge List Attributes
    ELEMENTS -> AttributeKeeper
    <REJECTED> -> AttributeRenamer
AttributeRenamer
    ATTR_TABLE = RENAME_SET_DEFAULT minus.href > href
    -> AttributeKeeper
ListExploder_plus
    INDEX_ATTR = _element_index_plus
    LIST_ATTR = plus{}
    ATTR_CONFLICT_RES = Use List Attribute Values
    ATTR_ACCUM_MODE = Merge List Attributes
    ELEMENTS -> AttributeKeeper
    <REJECTED> -> AttributeRenamer_2
AttributeKeeper
    KEEP_ATTRS = DP_Omrade.id,href
    -> AttributeTrimmer
AttributeTrimmer
    SRC_ATTRS = href
    TRIM_CHARS = #
    TRIM_TYPE = Both
    TRIM_TO_NONE = Yes
    -> FeatureMerger [REQUESTOR]
FeatureMerger
    JOIN_KEYS = @Value(href) @Value(gml_id) AUTO
    PROCESS_DUPS = No
    MERGE_TYPE = Geometry
    REJECT_NULL_MISSING_KEYS = No
    SUPPLIERS_FIRST = No
    MERGED -> AreaBuilder
AreaBuilder
    LINES_AS_SEGMENTS = No
    POLY_ACCUM_ATTRS_NAME = Use Attributes From One Feature
    CONSIDER_NODE_ELEVATION = no
    DROP_HOLES = Yes
    SNAPTYPE_PARAM = None
    CHECK_CURVE_DIRECTION = No
    ALLOW_CYCLES = No
    GROUP_BY = DP_Omrade.id
    CONNECT_Z_MODE = First Wins
    DONUT_CREATION = YES
    AREA -> VariableRetriever
VariableRetriever
    VARNAME = plan_uuid
    VALUE_ATTR = plan_uuid
    SCOPE = Global
    -> UUIDGenerator
UUIDGenerator
    UUID_ATTR = ey_uuid
    -> merge_yta_best [SUPPLIER]
AttributeRenamer_2
    ATTR_TABLE = RENAME_SET_DEFAULT plus.href > href

FME custom transformer extract_position

Parameters:
- INSATTNING.POINT.POS = @Value(insattning.Point.pos)   # insattning.Point.pos

AttributeSplitter_Input (input)
    -> AttributeSplitter
AttributeSplitter
    DROP_EMPTY_PARTS = No
    TRIM_OPTION = Both
    ATTR_NAME = insattning.Point.pos
    DELIMITER = " "
    LIST_NAME = _pos
    -> ListIndexer_2
ListIndexer_2
    PREFIX = n
    LIST_ATTR = _pos{}
    INDEX = 0
    -> ListIndexer_3
ListIndexer_3
    PREFIX = e
    LIST_ATTR = _pos{}
    INDEX = 1
    -> AttributeManager
AttributeManager
    ATTR_TABLE:
      REMOVE _pos{}
      RENAME_SET_VALUE n_pos > norr
      RENAME_SET_VALUE e_pos > ost
    -> ListIndexer_2_Output (output)
ListIndexer_2_Output (output)
